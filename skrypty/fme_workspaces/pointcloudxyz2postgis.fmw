FME workspace pointcloudxyz2postgis.fmw

Parameters:
- SourceDataset_POINTCLOUDXYZ = ""C:\Users\Tomasz\Downloads\wielkopolskie_grid100.zip" "C:\Users\Tomasz\Downloads\zachodniopomorskie_grid100.zip" "C:\Users\Tomasz\Downloads\warminsko-mazurskie_grid100.zip" "C:\Users\Tomasz\Downloads\swietokrzyskie_grid100.zip" "C:\Users\Tomasz\Downloads\slaskie_grid100.zip" "C:\Users\Tomasz\Downloads\pomorskie_grid100.zip" "C:\Users\Tomasz\Downloads\podlaskie_grid100.zip" "C:\Users\Tomasz\Downloads\mazowieckie_grid100.zip" "C:\Users\Tomasz\Downloads\podkarpackie_grid100.zip" "C:\Users\Tomasz\Downloads\opolskie_grid100.zip" "C:\Users\Tomasz\Downloads\malopolskie_grid100.zip" "C:\Users\Tomasz\Downloads\lodzkie_grid100.zip" "C:\Users\Tomasz\Downloads\lubelskie_grid100.zip" "C:\Users\Tomasz\Downloads\lubuskie_grid100.zip" "C:\Users\Tomasz\Downloads\kujawsko-pomorskie_grid100.zip" "C:\Users\Tomasz\Downloads\dolnoslaskie_grid100.zip""   # Point Cloud XYZ File(s)
- FEATURE_TYPES =
- DestDataset_POSTGIS = gis   # Database

Readers:
- POINTCLOUDXYZ_1: POINTCLOUDXYZ from $(SourceDataset_POINTCLOUDXYZ) in EPSG:2180

Writers:
- POSTGIS_1: POSTGIS to $(DestDataset_POSTGIS)

POINTCLOUDXYZ (reader POINTCLOUDXYZ_1)
    -> PointCloudCoercer
PointCloudCoercer
    ACCUM_ATTRS_NAME = No
    CONVERT_TO_DISPLAY = Individual Points
    POINT_COMPONENTS_PRESERVE_DISPLAY = Attributes
    COERCED -> nmt (writer POSTGIS_1)
nmt (writer POSTGIS_1)
