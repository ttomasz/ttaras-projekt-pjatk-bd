FME workspace nonxdsl.fmw

Parameters:
- SourceDataset_POSTGIS_3 = podyplomowka   # Connection
- DestDataset_POSTGRES = podyplomowka   # Connection
- SourceDataset_POSTGIS = podyplomowka   # Connection

Readers:
- POSTGIS_1: POSTGIS from $(SourceDataset_POSTGIS_3)
- POSTGIS_2: POSTGIS from $(SourceDataset_POSTGIS)

Writers:
- POSTGRES_1: POSTGRES to $(DestDataset_POSTGRES)

geowynik (reader POSTGIS_2)
    attributes: lokalnyid uuid, teryt_simc text, teryt_ulic text, nr text, no_of_neighbours int8, building_area float8, delta_z float8, median_z float8
    -> Reprojector
Reprojector
    DEST = EPSG:2180
    INTERPOLATION_TYPE_NAME = Nearest Neighbor
    RASTER_CELL_SIZE = Preserve Cells
    RASTER_TOLERANCE = 0.0
    SOURCE = EPSG:4326
    REPROJECTED -> NeighborFinder_3 [BASE]
geonodes_copper_nonxdsl (reader POSTGIS_1)
    -> Reprojector_2
Reprojector_2
    DEST = EPSG:2180
    INTERPOLATION_TYPE_NAME = Nearest Neighbor
    RASTER_CELL_SIZE = Preserve Cells
    RASTER_TOLERANCE = 0.0
    SOURCE = EPSG:4326
    REPROJECTED -> NeighborFinder_3 [CANDIDATE]
NeighborFinder_3
    ATTR_ACCUM_MODE = Merge Candidate
    ATTR_CONFLICT_RES = Use Base
    CANDIDATES_FIRST = Yes
    INSERT_VERTEX = No
    K = 1
    MAX = 20000
    MEASURES_FROM_CANDIDATE = No
    MEASURE_TYPE = Continuous
    MODE = Bases and Candidates
    TREAT_POLYGON_AS = Lines
    MATCHED -> AttributeManager_3
AttributeManager_3
    ATTR_TABLE:
      RENAME_SET_VALUE _distance > distance_copper_nonxdsl
      REMOVE _angle
      REMOVE _candidate_angle
      REMOVE _candidate_label_angle
      REMOVE _closest_candidate_x
      REMOVE _closest_candidate_y
      REMOVE _closest_base_x
      REMOVE _closest_base_y
    -> GeometryRemover
GeometryRemover
    -> copper_nonxdsl (writer POSTGRES_1)
copper_nonxdsl (writer POSTGRES_1)
    attributes: lokalnyid uuid, distance_copper_nonxdsl numeric(10,2)
