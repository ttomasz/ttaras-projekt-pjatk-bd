FME workspace citygml2postgis.fmw

Parameters:
- SourceDataset_CITYGML = C:\Users\Tomasz\Downloads\lod1_downloads\http_download_15734077319_14356.zip   # Source CityGML File(s)
- FEATURE_TYPES =
- DestDataset_POSTGIS = gis   # Database
- DestDataset_GEOPACKAGE = $(FME_MF_DIR)temp\lod1_buildings.gpkg   # GeoPackage File

Readers:
- CITYGML_1: CITYGML from $(SourceDataset_CITYGML) in EPSG:2180

Writers:
- POSTGIS_1: POSTGIS to $(DestDataset_POSTGIS) in EPSG:2180
- GEOPACKAGE_1: GEOPACKAGE to $(DestDataset_GEOPACKAGE)

CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer, citygml_measured_height xml_real64, citygml_interior_room{}.xlink_href xml_buffer, citygml_class xml_buffer, externalReference{}.externalObject.name xml_xml, citygml_bounded_by{}.xlink_href xml_buffer, citygml_appearance{}.xlink_href xml_buffer, externalReference{}.informationSystem xml_xml, citygml_level_of_detail{} xml_buffer, przestNazw xml_buffer, citygml_feature_role_attr_val xml_buffer, citygml_class_codeSpace xml_buffer, citygml_function{} xml_buffer, citygml_generalizes_to{}.xlink_href xml_buffer, citygml_outer_building_installation{}.xlink_href xml_buffer, citygml_interior_building_installation{}.xlink_href xml_buffer, wersjaId xml_buffer, citygml_storeys_below_ground xml_uint64, citygml_usage{} xml_buffer, citygml_storey_heights_above_ground_units xml_buffer, citygml_feature_role_attr_name xml_buffer, citygml_year_of_construction xml_buffer, citygml_storey_heights_above_ground xml_buffer, citygml_roof_type xml_buffer, externalReference{}.externalObject.uri xml_xml,
      citygml_storeys_above_ground xml_uint64, buildingId xml_buffer, citygml_relative_to_terrain xml_char(33), citygml_year_of_demolition xml_buffer, citygml_feature_role xml_buffer, aktZrodla xml_buffer, citygml_function{}.codeSpace xml_buffer, citygml_consists_of_building_part{}.xlink_href xml_buffer, citygml_usage{}.codeSpace xml_buffer, zrodloDach xml_buffer, citygml_storey_heights_below_ground_units xml_buffer, citygml_roof_type_codeSpace xml_buffer, citygml_creationDate xml_date, citygml_address{}.xlink_href xml_buffer, citygml_storey_heights_below_ground xml_buffer, citygml_relative_to_water xml_char(38), citygml_measured_height_units xml_buffer, citygml_terminationDate xml_date
    -> 2DForcer
2DForcer
    2D -> GeometryPartExtractor
GeometryPartExtractor
    GQUERY:
      for $geom in //geometry
      where $geom/@fme_geometry_type = 'IFMEPolygon'
      return number($geom/@fme_id)
    EXTRACTED -> DuplicateFilter
DuplicateFilter
    INPUT_ORDERED_CHOICE = Yes
    KEYATTR = gml_id
    UNIQUE -> GeometryCoercer
GeometryCoercer
    GQUERY:
      for $geom in //geometry
      where $geom/count(parent::geometry) = 0
      return number($geom/@fme_id)
    KIND = fme_polygon
    COERCED -> lod1_buildings (writer GEOPACKAGE_1)
    UNTOUCHED -> lod1_buildings (writer GEOPACKAGE_1)
lod1_buildings (writer GEOPACKAGE_1)
lod1_buildings (writer POSTGIS_1) [off]
