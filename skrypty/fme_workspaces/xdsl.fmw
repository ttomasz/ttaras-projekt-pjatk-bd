FME workspace xdsl.fmw

Parameters:
- SourceDataset_POSTGIS = podyplomowka   # Connection
- SourceDataset_POSTGIS_3 = podyplomowka   # Connection
- DestDataset_POSTGRES = podyplomowka   # Connection

Readers:
- POSTGIS_1: POSTGIS from $(SourceDataset_POSTGIS)
- POSTGIS_2: POSTGIS from $(SourceDataset_POSTGIS_3)

Writers:
- POSTGRES_1: POSTGRES to $(DestDataset_POSTGRES)

geowynik (reader POSTGIS_2)
    attributes: lokalnyid uuid, teryt_simc text, teryt_ulic text, nr text, no_of_neighbours int8, building_area float8, delta_z float8, median_z float8
    -> Reprojector_2
Reprojector_2
    DEST = EPSG:2180
    INTERPOLATION_TYPE_NAME = Nearest Neighbor
    RASTER_CELL_SIZE = Preserve Cells
    RASTER_TOLERANCE = 0.0
    SOURCE = EPSG:4326
    REPROJECTED -> NeighborFinder_4 [BASE]
geonodes_copper_xdsl (reader POSTGIS_1)
    -> Reprojector_3
Reprojector_3
    DEST = EPSG:2180
    INTERPOLATION_TYPE_NAME = Nearest Neighbor
    RASTER_CELL_SIZE = Preserve Cells
    RASTER_TOLERANCE = 0.0
    SOURCE = EPSG:4326
    REPROJECTED -> NeighborFinder_4 [CANDIDATE]
NeighborFinder_4
    ATTR_ACCUM_MODE = Merge Candidate
    ATTR_CONFLICT_RES = Use Base
    CANDIDATES_FIRST = Yes
    INSERT_VERTEX = No
    K = 1
    MAX = 20000
    MEASURES_FROM_CANDIDATE = No
    MEASURE_TYPE = Continuous
    MODE = Bases and Candidates
    TREAT_POLYGON_AS = Lines
    MATCHED -> AttributeManager_4
AttributeManager_4
    ATTR_TABLE:
      RENAME_SET_VALUE _distance > distance_copper_xdsl
      REMOVE _angle
      REMOVE _candidate_angle
      REMOVE _candidate_label_angle
      REMOVE _closest_candidate_x
      REMOVE _closest_candidate_y
      REMOVE _closest_base_x
      REMOVE _closest_base_y
    -> GeometryRemover_2
GeometryRemover_2
    -> copper_xdsl (writer POSTGRES_1)
copper_xdsl (writer POSTGRES_1)
    attributes: lokalnyid uuid, distance_copper_xdsl numeric(10,2)
